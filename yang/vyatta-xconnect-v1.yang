module vyatta-xconnect-v1 {
	namespace "urn:vyatta.com:mgmt:vyatta-xconnect:1";
	prefix vyatta-xconnect-v1;

	import configd-v1 {
		prefix configd;
	}
	import vyatta-interfaces-dataplane-v1 {
		prefix interfaces-dataplane;
	}

	organization "AT&T Inc.";
	contact
		"AT&T
                 Postal: 208 S. Akard Street
                         Dallas, Tx 25202
                 Web: www.att.com";

	description
		"Copyright (c) 2019, AT&T Intellectual Property.
		 All rights reserved.

		 Copyright (c) 2015-2016 by Brocade Communications Systems, Inc.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 The YANG module for vyatta-xconnect-v1";

	revision 2016-06-17 {
		description "Add configd pattern help for vhost interface.";
	}

	revision 2016-03-16 {
		description "Single quote the regex patterns";
	}

	revision 2015-12-07 {
		description "Initial revision of version 1.";
	}

	grouping xconnect-if-binding {
		container xconnect {
			configd:help "Cross-Connect Interface Binding";
			configd:priority "525";
			configd:end "/opt/vyatta/share/tmplscripts/interfaces/dataplane/xconnect/configd_end.sh";
			configd:validate "/opt/vyatta/share/tmplscripts/interfaces/dataplane/xconnect/configd_validate.cli";
			leaf ttl {
				type uint8 {
					range 1..127;
				}
				configd:help "TTL value";
			}
			leaf l2tpeth {
				type string {
					pattern 'lttp[0-9]+';
					configd:pattern-help "<lttpN>";
				}
				configd:help "L2tpeth interface name";
				configd:validate "/opt/vyatta/share/tmplscripts/interfaces/dataplane/xconnect/l2tpeth/configd_validate1.cli";
			}
			leaf dataplane {
				configd:help "Dataplane interface name";
				type union {
				     type interfaces-dataplane:dataplane-ifname;
				     type interfaces-dataplane:dataplane-vifname;
				}
			}
			leaf vhost {
				configd:help "Virtio vhost devices";
				type union {
				     type string {
				     	  pattern 'dp[0-9]+vhost[0-9]+';
				     	  configd:pattern-help "<dpNvhostN>";
				     }
				     type string {
				     	  pattern 'dp[0-9]+vhost[0-9]+\.[1-9][0-9]*';
				     	  configd:pattern-help "<dpNvhostN.N>";
				     }
				}
			}
		}
	}
}
